FME workspace Traitement.fmw

Parameters:
- SourceDataset_XLSXR = D:\SIG\Dropbox (Vélo&Territoires)\7_Expertise\2-Enquête Territoires\2019\02_REPONSES A L'ENQUETE\04_RESULTATS COMPLETS\2019-07-01_Résultats complets traités.xlsx   # Fichier(s) source Microsoft Excel 
- SourceDataset_ESRISHAPE_10 = D:\SIG\Dropbox (Vélo&Territoires)\1_ON3V\NAS\06_CARTES_ANALYSE_ON3V\Enquête_Territoires\2019\dossier Qgis\couche ADMIN\epci.shp   # Source Esri Shapefile(s)
- SourceDataset_ESRISHAPE = D:\SIG\Dropbox (Vélo&Territoires)\1_ON3V\NAS\06_CARTES_ANALYSE_ON3V\Enquête_Territoires\2019\dossier Qgis\couche ADMIN\region.shp   # Shapefile(s) Esri source 
- SourceDataset_ESRISHAPE_9 = D:\SIG\Dropbox (Vélo&Territoires)\1_ON3V\NAS\06_CARTES_ANALYSE_ON3V\Enquête_Territoires\2019\dossier Qgis\couche ADMIN\departement.shp   # Source Esri Shapefile(s)
- SourceDataset_ESRISHAPE_5 = D:\SIG\Dropbox (Vélo&Territoires)\1_ON3V\NAS\05_AUTRES_BD\IGN\2019\ADMIN-EXPRESS_2-0__SHP__FRA_2019-03-14\ADMIN-EXPRESS\1_DONNEES_LIVRAISON_2019-03-14\ADE_2-0_SHP_LAMB93_FR\COMMUNE.shp   # Shapefile(s) Esri source 
- DestDataset_GEOJSON = $(FME_MF_DIR)DEPARTEMENT.geojson   # Fichiers GeoJSON Destination 
- DestDataset_GEOJSON_5 = $(FME_MF_DIR)REGION.geojson   # Fichiers GeoJSON Destination 
- DestDataset_GEOJSON_7 = $(FME_MF_DIR)EPCI_POLY.geojson   # Fichiers GeoJSON Destination 
- DestDataset_GEOJSON_6 = $(FME_MF_DIR)AUTRE.geojson   # Fichiers GeoJSON Destination 

Readers:
- XLSXR_1: XLSXR from $(SourceDataset_XLSXR)
- ESRISHAPE_1: ESRISHAPE from $(SourceDataset_ESRISHAPE_10)
- ESRISHAPE_2: ESRISHAPE from $(SourceDataset_ESRISHAPE)
- ESRISHAPE_3: ESRISHAPE from $(SourceDataset_ESRISHAPE_9)
- ESRISHAPE_4: ESRISHAPE from $(SourceDataset_ESRISHAPE_5)

Writers:
- GEOJSON_1: GEOJSON to $(DestDataset_GEOJSON)
- GEOJSON_2: GEOJSON to $(DestDataset_GEOJSON_5)
- GEOJSON_3: GEOJSON to $(DestDataset_GEOJSON_7)
- GEOJSON_4: GEOJSON to $(DestDataset_GEOJSON_6)

ENQUÊTE TERRITOIRES 2019 (reader XLSXR_1)
    attributes: ID de la réponse number(5,0), Réponse char(4), Date de soumission char(20), Dernière page number(3,0), Langue de départ char(3), Tête de série number(11,0), Date de lancement char(20), Date de la dernière action char(20), Nom de la collectivité : char(58), Code géographique : number(10,0), Population char(9), A1_SQ002_. Code postal du siège : number(6,0), Département :  char(24), Région  char(27), Nature juridique char(12), Détail : char(27), A3_SQ001_. _Prénom :_ char(18), A3_SQ002_. _Nom :_ char(38), A3_SQ003_. _Titre/poste :_ char(95), A3_SQ004_. _Direction/service :_ char(128), A4_SQ002_. _Adresse mail :_ char(48), A4_SQ003_  _Téléphone :_ char(11), B5. Action sur le vélo ? char(9), B5bis. Si non, pourquoi ? char(728), B6. Compétence voirie ?  char(4), B6a_SQ001_. Intérêt communautaire ?  _Schéma directeur cyclable_ char(4), B6a_SQ003_. Intérêt communautaire ?  _Aménagement d’itinéraires_ char(4), B6a_SQ004_. Intérêt communautaire ?  _Coordination et programmation_ char(4), B6a_SQ005_. Intérêt communautaire ?  _Équipements_ char(4), Stratégie de planification vélo : char(9),
      Forme de la stratégie : char(3647), C8b_SQ001_. En quelle année a-t-elle été adoptée ?  _Première adoption :_ char(4), C8b_SQ001_. Première adoption ? char(222), C8b_SQ001__ANNEE. Première adoption_année char(222), C8b_SQ002_. En quelle année a-t-elle été adoptée ?  _Dernière mise à jour :_ char(4), C8b_SQ002_. Dernière mise à jour ? char(92), C8b_SQ002__ANNEE. Dernière mise à jour_Année char(75), C8c_SQ001_. Thématiques abordées ? _Économie_ char(4), C8c_SQ002_. Thématiques abordées ? _Habitat_ char(4), C8c_SQ003_. Thématiques abordées ? _Infrastructure/aménagement_ char(4), C8c_SQ004_. Thématiques abordées ? _Insertion_ char(4), C8c_SQ005_. Thématiques abordées ? _Micro-mobilité_ char(4), C8c_SQ006_. Thématiques abordées ? _Mobilité_ char(4), C8c_SQ007_. Thématiques abordées ? _Qualité de l’air_ char(4), C8c_SQ008_. Thématiques abordées ? _Santé_ char(4), C8c_SQ009_. Thématiques abordées ? _Scolaire_ char(4), C8c_SQ010_. Thématiques abordées ? _Sécurité_ char(4), C8c_SQ011_. Thématiques abordées ? _Solidarité_ char(4), C8c_SQ012_. Thématiques abordées ? _Sport_ char(4), C8c_SQ013_. Thématiques abordées ? _Stationnement_ char(4), C8c_SQ014_. Thématiques abordées ? _Tourisme_ char(4), C8c_other_. Thématiques abordées ? _Autre_ char(85), C8d. D’autres acteurs ont-ils participé à l’élaboration de ce document ? char(4), C8d1_SQ001_. _Union Européenne_ char(4), C8d1_SQ002_. _État (ex : DREAL, ou autres services déconcentrés)_ char(4), C8d1_SQ003_. _Ademe_ char(4), C8d1_SQ004_. _Régions_ char(4), C8d1_SQ005_. _Départements_ char(4), C8d1_SQ006_. _Groupements de communes_ char(4), C8d1_SQ007_. _Communes_ char(4),
      C8d1_SQ008_. _CRT/CDT/OT _ char(4), C8d1_SQ009_. _Associations_ char(4), C8d1_SQ011_. _Entreprises_ char(4), C8d1_SQ010_. _Citoyens_ char(4), C8d1_other_. _Autre_ char(381), C8e. Ce document fait-il référence à d’autres schémas vélo structurants ? char(4), C8e1_SQ001_. _Schéma EuroVelo_ char(4), C8e1_SQ002_. _Schéma National Véloroutes et Voies Vertes_ char(4), C8e1_SQ003_. _Schéma Régional Véloroutes et Voies Vertes_ char(4), C8e1_SQ004_. _Schémas Départementaux Véloroutes et Voies Vertes_ char(4), C8e1_SQ005_. _Schémas intercommunaux et communaux_ char(4), C8e1_SQ006_. _Autres schémas locaux_ char(4), C8f. Si le document finalisé est accessible, pourriez-vous le déposer ici ?  char(823), C8f_filecount_. Nombre de document déposés ?  number(2,0), C9. La collectivité participe-t-elle à un ou plusieurs comités d’itinéraires ? char(4), C9a_SQ001_. _EV1 | La Vélodyssée _ char(4), C9a_SQ002_. _EV3 | La Scandibérique_ char(4), C9a_SQ003_. _EV4_ char(4), C9a_SQ004_. _EV5 | Via Romea (Francigena) _ char(4), C9a_SQ005_. _EV6 | EuroVelo 6_ char(4), C9a_SQ006_. _La Loire à vélo (partie d'EV6) _ char(4), C9a_SQ007_. _EV8 | La Méditerranée à vélo _ char(4), C9a_SQ008_. _EV15 | Véloroute Rhin _ char(4), C9a_SQ009_. _EV17 | ViaRhôna _ char(4), C9a_SQ018_. _EV19 | La Meuse à vélo _ char(4), C9a_SQ010_. _Avenue verte London-Paris (partie de la V16)_ char(4), C9a_SQ012_. _V33 | La Seine à Vélo _ char(4), C9a_SQ013_. _V40 | La Véloscénie_ char(4), C9a_SQ014_. _V41 | Saint-Jacques à Vélo_ char(4), C9a_SQ015_. _V43 | La Vélo Francette_ char(4),
      C9a_SQ016_. _V50 | L'Échappée bleue_ char(4), C9a_SQ017_. _V51 | Tour de Bourgogne à Vélo _ char(4), C9a_SQ019_. _V62 et V63 | Véloroutes du Sillon Alpin _ char(4), C9a_SQ021_. _V70_ char(4), C9a_SQ023_. _Via Fluvia | partie de la V73 _ char(4), C9a_SQ029_. _V80 | Canal des 2 Mers à Vélo_ char(4), C9a_SQ024_. _V84 | Passa Païs_ char(4), C9a_SQ025_. _V86 | La Vallée du Lot à Vélo _ char(4), C9a_SQ026_. _V92 | La Flow Vélo _ char(4), C9a_SQ027_. _La Dolce Via (Ardèche)_ char(4), C9a_SQ028_. _L'Indre à Vélo (Centre Val de Loire) _ char(4), C10. Participe-t-elle à des réseaux, locaux ou nationaux, ayant pour but de développer le vélo ? char(4), C10a_V1_. _Vélo & Territoires_ char(4), C10a_V2_. _Club des Villes et des Territoires Cyclables_ char(4), C10a_other_. _Autre_ char(122), Élu référent vélo au sein de la collectivité : char(4), C11a_SQ001_. Quelle délégation politique ?  _Attractivité/communication_ char(4), C11a_SQ002_. Quelle délégation politique ?  _Culture_ char(4), C11a_SQ003_. Quelle délégation politique ?  _Économie/finances_ char(4), C11a_SQ004_. Quelle délégation politique ?  _Environnement_ char(4), C11a_SQ005_. Quelle délégation politique ?  _Habitat_ char(4), C11a_SQ006_. Quelle délégation politique ?  _Infrastructures_ char(4), C11a_SQ007_. Quelle délégation politique ?  _Parcs et jardins_ char(4), C11a_SQ008_. Quelle délégation politique ?  _Ruralité/Terroirs_ char(4), C11a_SQ009_. Quelle délégation politique ?  _Sports_ char(4), C11a_SQ010_. Quelle délégation politique ?  _Tourisme_ char(4), C11a_SQ011_. Quelle délégation politique ?  _Transports/Déplacements/Mobilités_ char(4), C11a_SQ012_. Quelle délégation politique ?  _Urbanisme_ char(4), C11a_SQ013_. Quelle délégation politique ?  _Voirie/routes_ char(4), C11a_other_. Quelle délégation politique ?  _Autre_ char(136),
      C12. Commentaires : char(736), D13. La collectivité dispose-t-elle d’une cellule technique spécifiquement dédiée au vélo ? char(4), D13a_SQ001_. Direction ? _Aménagement du territoire/urbanisme_ char(4), D13a_SQ002_. Direction ? _Culture_ char(4), D13a_SQ003_. Direction ? _Développement durable_ char(4), D13a_SQ004_. Direction ? _Environnement/biodiversité_ char(4), D13a_SQ005_. Direction ? _Équipements_ char(4), D13a_SQ006_. Direction ? _Observation/études_ char(4), D13a_SQ007_. Direction ? _Sports/Loisirs_ char(4), D13a_SQ008_. Direction ? _Tourisme_ char(4), D13a_SQ009_. Direction ? _Transports/déplacements/mobilité_ char(4), D13a_SQ010_. Direction ? _Voirie/routes_ char(4), D13a_other_. Direction ? _Autre_ char(161), D13b. Sinon, comment et par qui la politique vélo est-elle mis en oeuvre ? char(1325), Nombre d’équivalents temps plein (ETP) consacrés au vélo : number(7,2), D15. Détaillez si nécessaire : char(1197), D16_SQ001_SQ001_. Budget de fonctionnement total annuel ? _2018_ char(11), D16_SQ001_SQ002_. Budget de fonctionnement total annuel ? _2019_ char(11), D16_SQ002_SQ001_. Budget d'investissement total annuel ? _2018_ char(11), D16_SQ002_SQ002_. Budget d'investissement total annuel ? _2019_ char(11), Budget spécifiquement dédié au vélo : char(4), Chiffres budget vélo ?  char(4), D17a_SQ001_SQ001_. Budget de fonctionnement annuel vélo ? _2018 (budget clos)_ char(8), D17a_SQ001_SQ002_. Budget de fonctionnement annuel vélo ? _2019 (budget en cours)_ char(8), D17a_SQ002_SQ001_. Budget d'investissement annuel vélo ? _2018 (budget clos)_ char(10), D17a_SQ002_SQ002_. Budget d'investissement annuel vélo ? _2019 (budget en cours)_ char(9), Total budget 2018 char(9), Total budget 2019 char(9), D18. Commentaires : char(1270), E19. La collectivité a-t-elle participé à l’élaboration de la politique cyclable d’autres collectivités ? char(4),
      E19a_SQ001_. _Régions_ char(4), E19a_SQ002_. _Départements_ char(4), E19a_SQ003_. _Métropoles_ char(4), E19a_SQ004_. _Communautés urbaines_ char(4), E19a_SQ005_. _Communautés d’agglomération_ char(4), E19a_SQ006_. _Communautés de communes_ char(4), E19a_SQ007_. _Communes_ char(4), E19a_other_. _Autre_ char(110), E20. La collectivité anime-t-elle une ou plusieurs instances de concertation et de dialogue en rapport avec le vélo sur le territoire ? char(4), E20a. Si oui, pouvez-vous préciser ?  char(431), E21. La collectivité implique-t-elle des associations d’usagers vélo dans l’élaboration de ses politiques cyclables ? char(4), E21a_SQ001_. _Implication ponctuelle_ char(4), E21a_SQ002_. _Réunions régulières dédiées_ char(4), E21a_SQ003_. _Subventions_ char(4), E21a_other_. _Autre_ char(308), E22. En 2018, la collectivité a subventionné les projets vélo d'autres collectivités ? char(4), E22a. Infrastructures - Départements ? number(8,0), E22a Infrastructures - EPCI ? char(8), E22a Infrastructures - Communes ? char(8), E22a Services - Départements ? number(6,0), E22a Services - EPCI ? number(6,0), E22a Services - Communes ? number(6,0), E22a Promotion et valorisation - Départements ? number(6,0), E22a Promotion et valorisation - EPCI ? number(6,0), E22a Promotion et valorisation - Communes? number(6,0), E22a Total - Départements  number(8,0), E22a Total - EPCI char(8), E22a Total - Communes char(8), E22b. Sous quelles conditions la collectivité a-t-elle accordé ces fonds ? char(2035), E23. En 2018, la collectivité a-t-elle bénéficié de financements externes pour ses projets vélo ? char(4),
      E23a Ingénierie et études - UE ? number(6,0), E23a Ingénierie et études - État et organismes rattachés ? char(7), E23a Ingénierie et études - Régions ? char(7), E23a Ingénierie et études - Département ? number(6,0), E23a Infrastructures - UE ? char(8), E23a Infrastructures - État et organismes rattachés? char(8), E23a Infrastructures - Régions? char(8), E23a Infrastructures - Département ? char(8), E23a Services - UE ? number(6,0), E23a Services - État et organismes rattachés? char(7), E23a Services - Régions ? number(5,0), E23a Services - Département ? char(7), E23a Promotion et valorisation - UE ? char(7), E23a Promotion et valorisation - État et organismes rattachés ? number(6,0), E23a Promotion et valorisation - Régions ? number(6,0), E23a Promotion et valorisation - Département ? number(5,0), E23a Total - UE ? char(8), E23a Total - État et organsimes rattachés ? char(8), E23a Total - Régions ? char(8), E23a Total - Département ? char(8), E24. Commentaires : char(727), F25. La collectivité agit-elle en maîtrise d’ouvrage directe pour la réalisation d’aménagements cyclables ?   char(4), F26. A-t-elle mis en place une charte des aménagements cyclables ? char(4), F26a_SQ001_. En quelle année ce document a-t-il été adopté ?  char(4), F26a_SQ001comment_.  _Première adoption : _ char(486), F26a_SQ002_. En quelle année ce document a-t-il été adopté ?   char(4), F26a_SQ002comment_. _Dernière mise à jour : _ char(78), F26b. Si le document finalisé est accessible, pourriez-vous le déposer ici ?  char(573), F26b_filecount_. filecount - Si le document finalisé est accessible, pourriez-vous le déposer ici ?  number(2,0), F27. La collectivité réalise-t-elle un suivi annuel des ouvertures d’aménagements cyclables sur son territoire ? char(4),
      F27a_SQ001_SQ001_. Linéaires d’aménagements cyclables réalisés (km/an) ? _2015_ char(61), F27a_SQ002_SQ001_. Linéaires d’aménagements cyclables réalisés (km/an) ? _2016_ char(84), F27a_SQ003_SQ001_. Linéaires d’aménagements cyclables réalisés (km/an) ? _2017_ char(66), F27a_SQ004_SQ001_. Linéaires d’aménagements cyclables réalisés (km/an) ? _2018_ char(35), F27a_SQ005_SQ001_. Linéaires d’aménagements cyclables réalisés (km/an) ?  _2019_ char(66), F27b. Merci d'expliciter ces chiffres si nécessaire : char(1131), F28. La collectivité dispose-t-elle de ratios de coûts moyens de réalisation des aménagements cyclables sur son territoire ? char(4), F28a. Quels sont-ils ? char(478), F29. La collectivité est-elle en charge de l’entretien d’aménagements cyclables sur son territoire ? char(10), F29a. Comment cet entretien est-il organisé ? char(1134), F29b. La collectivité dispose-t-elle de ratios de coûts moyens d’entretien des aménagements cyclables sur son territoire ? char(4), F29b1. Quels sont-ils ? char(344), F30. Commentaires : char(711), G31. La collectivité dispose-t-elle d’un système d’information géographique (SIG) intégrant les aménagements cyclables ? char(4), G31a. Ces données sont-elles disponibles en Open Data ? char(4), G31b. Ces données sont-elles transmises à l’Observatoire national des véloroutes et voies vertes (ON3V) de Vélo & Territoires ? char(4), G31b1_SQ001_. Pourquoi ? _Méconnaissance de l’outil_ char(4), G31b1_SQ002_. Pourquoi ? _Outil peu pratique/trop complexe_ char(4), G31b1_SQ003_. Pourquoi ? _Manque de temps_ char(4), G31b1_SQ004_. Pourquoi ? _Données disponibles en Open Data_ char(4), G31b1_other_. Pourquoi ? _Autre_ char(183), G31c. Utilisez-vous l’Observatoire national des véloroutes et voies vertes (ON3V) de Vélo & Territoires comme outil de suivi géomatique ? char(4), G32. Commentaires : char(1301), H33. La collectivité a-t-elle mis en place une signalisation directionnelle vélo sur son territoire ? char(4), H34. A-t-elle développé un plan de jalonnement vélo ou schéma directeur de signalisation ? char(4), H34a. Si le document finalisé est accessible, pourriez-vous le déposer ici ?  char(704), H34a_filecount_. filecount - Si le document finalisé est accessible, pourriez-vous le déposer ici ?  number(2,0), H35. La collectivité dispose-t-elle d’une ou plusieurs charte(s) graphique(s) de signalisation vélo ? char(4), H35a. Respecte(nt)-elle(s) le référentiel national datant de 2013 (fiche n°28 du Cerema) ? char(4), H36. Commentaires : char(783),
      I37. La collectivité propose-t-elle des places de stationnement vélo sur son territoire ? char(4), I37a_SQ001_SQ001_. Nombre de places de stationnement ?  _Arceaux de stationnement_ char(131), I37a_SQ002_SQ001_. Nombre de places de stationnement ?  _Abris individuels sécurisées_ char(67), I37a_SQ003_SQ001_. Nombre de places de stationnement ?  _Abris collectifs sécurisés_ char(53), I37a_SQ004_SQ001_. Nombre de places de stationnement ?  _Abris non sécurisés_ char(86), I37a_SQ005_SQ001_. Nombre de places de stationnement ?  _Global_ char(239), I37b_SQ001_. Stationnements à proximité ?  _Aires de covoiturage_ char(10), I37b_SQ002_. Stationnements à proximité ?  _Gares/pôles multimodaux_ char(10), I37b_SQ003_. Stationnements à proximité ?  _Arrêts de transports publics urbains et interurbains_ char(10), I38_SQ001_. Service d’embarquement ? _Trains_ char(4), I38_SQ002_. Service d’embarquement ? _Cars_ char(4), I38_SQ003_. Service d’embarquement ? _Bus_ char(4), I38_SQ004_. Service d’embarquement ? _Tramways_ char(4), I38_SQ005_. Service d’embarquement ? _Métro_ char(4), I38_SQ006_. Service d’embarquement ? _Transports à la demande_ char(4), I39. Commentaires : char(746), J40_SQ001_.  _Vélo en location humanisée courte ou longue durée_ char(4), J40_SQ002_. _Vélo en libre-service (VLS)_ char(4), J40_SQ003_. _Prêt de vélo (gratuit sous caution)_ char(4), J41. Existe-t-il un service de location de vélo en free-floating (VFF) sur le territoire de votre collectivité ? char(4), J42. La collectivité propose-t-elle une aide à l’achat de vélos (tous types de vélos confondus) ? char(4), J42a_SQ001_SQ001_. Montant de l'aide ?  _Vélo standards_ char(18), J42a_SQ002_SQ001_. Montant de l'aide ?  _VAE _ char(134), J42a_SQ003_SQ001_. Montant de l'aide ?  _Vélos pliants _ char(37), J42a_SQ004_SQ001_. Montant de l'aide ?  _Vélos-cargos/familiaux_ char(37), J43. La collectivité a-t-elle mis en place une indemnité kilométrique vélo (IKV) à destination de ses agents ? char(4), J43a_SQ001_. _Montant (€/km) :_ char(42), J43a_SQ002_. _Plafond :_ char(48), J44. Commentaires : char(859), K45. La collectivité a-t-elle ciblé des actions sur le tourisme à vélo ? char(4),
      K45a_SQ001_. Via ? _Association indépendante dédiée_ char(4), K45a_SQ002_. Via ? _Organisme local du tourisme (CRT, ADT/CDT, OT, etc.)_ char(4), K45a_SQ003_. Via ? _Services « tourisme » de la collectivité_ char(4), K45a_other_. Via ? _Autre_ char(301), K45b_SQ001_. Actions de marketing touristique « vélo » ? _Carte touristique généraliste_ char(4), K45b_SQ002_. Actions de marketing touristique « vélo » ? _Référencement sur France Vélo Tourisme_ char(4), K45b_SQ003_. Actions de marketing touristique « vélo » ? _Organisation d’événements dédiés au tourisme à vélo_ char(4), K45b_SQ004_. Actions de marketing touristique « vélo » ? _Participation à des événements dédiés au tourisme à vélo_ char(4), K45b_SQ005_. Actions de marketing touristique « vélo » ? _Site(s) web dédié(s) _ char(4), K45b_SQ006_. Actions de marketing touristique « vélo » ? _Support papier spécifique_ char(4), K45b_SQ007_. Actions de marketing touristique « vélo » ? _Voyages de presse/accueils de presse_ char(4), K45b_SQ008_. Actions de marketing touristique « vélo » ? _Topo-guide_ char(4), K45b_other_. Actions de marketing touristique « vélo » ? _Autre_ char(199), K45c. La marque Accueil Vélo © (ou équivalent) est-elle déployée sur le territoire de la collectivité ? char(6), K45c_other_. La marque Accueil Vélo © (ou équivalent) est-elle déployée sur le territoire de la collectivité ? _Autre_ char(45), K46. Commentaires : char(1622), L47. La collectivité a-t-elle mis en place une politique de communication spécifique au vélo (tous usages confondus et pas seulement touristiques) ? char(4), L47a_SQ001_. Sous quelle forme ?  _Application mobile_ char(4), L47a_SQ002_. Sous quelle forme ?  _Site(s) web dédié(s)_ char(4), L47a_SQ003_. Sous quelle forme ?  _Evènement vélo grand public (fête du vélo, slow-up, etc.)_ char(4), L47a_SQ004_. Sous quelle forme ?  _Cartographie (papier ou numérique) publique des itinéraires cyclables_ char(4), L47a_SQ006_. Sous quelle forme ?  _Campagne d'affichage_ char(4), L47a_SQ005_. Sous quelle forme ?  _Campagne de promotion _ char(4), L47a_other_. Sous quelle forme ?  _Autre_ char(125), L48. La collectivité a-t-elle développé une structure d’accueil et d’information dédiée aux usagers vélo ? char(4), L49. La collectivité a-t-elle mis en place un Plan de déplacement administration (PDA) ? char(4), L49a. Ce PDA comprend-il un volet concernant le vélo ? char(4), L50. La collectivité mène-t-elle une politique de sensibilisation à la sécurité routière spécifique aux vélos ? char(4), L51. Accompagne-t-elle sur son territoire le développement de vélo-écoles ? char(4), L52. Mène-t-elle une politique de sensibilisation contre le vol de vélo ? char(4),
      L52a. Cette sensibilisation intègre-t-elle le marquage Bicycode © ? char(4), L53. La collectivité soutient-elle la mise en place d’ateliers de réparation de vélos sur son territoire ? char(4), L54. Commentaires : char(634), M55. À ce jour, la collectivité dispose-t-elle d’une estimation de la part modale du vélo sur son territoire ? char(4), M55a_SQ001_. _Part modale du vélo : _ char(80), M55a_SQ002_. Pourriez-vous préciser, pour la dernière en date : _Date de l'estimation :_ char(37), M55a_SQ003_. _Source de l'estimation :_ char(156), M56. La collectivité dispose-t-elle de compteurs vélo permanents ? char(4), M56a. Combien ?  number(3,0), M56b. Partage-t-elle les données de ces compteurs avec la Plateforme nationale des fréquentations (PNF) de Vélo & Territoires ? char(4), M56b1_SQ001_. Si non, pourquoi ? _Méconnaissance de l’outil_ char(4), M56b1_SQ002_. Si non, pourquoi ? _Outil peu pratique/trop complexe_ char(4), M56b1_SQ003_. Si non, pourquoi ? _Manque de temps_ char(4), M56b1_SQ004_. Si non, pourquoi ? _Données disponibles en Open Data_ char(4), M56b1_other_. Si non, pourquoi ? _Autre_ char(73), M57. La collectivité réalise-t-elle des comptages ponctuels ? char(4), M58. A-t-elle réalisé des enquêtes de fréquentation pour évaluer les retombées économiques de ses itinéraires cyclables ? char(4), M59_SQ001_. Autres moyens ? _Enquête mobilité certifiée Cerema EMC² (anciennement EMD) _ char(4), M59_other_. Autre moyens ? _Autre_ char(157), M60. Commentaires : char(772), N61. Selon vous, quels sont les grands défis à venir pour la politique cyclable de la collectivité ? char(1706), N62. Commentaires : char(1019), O63. Confirmez-vous avoir répondu à l'ensemble des questions souhaitées ? Passé ce point, vous ne pourrez plus revenir en arrière pour modifier vos réponses. char(27)
    -> AttributeKeeper
AttributeKeeper
    KEEP_ATTRS = A1_SQ002_. Code postal du siège :,Stratégie de planification vélo :,Nom de la collectivité :,Nature juridique,Code géographique :
    -> AttributeValueMapper
AttributeValueMapper
    DIRECTION = Forward (Source To Destination)
    LUT = Commune,C,Département,D,EPCI,I,Région,R
    SRC = Nature juridique
    VAL_ATTR = Statut
    -> AttributeManager
AttributeManager
    ATTR_TABLE:
      RENAME_SET_VALUE Nom de la collectivité : > NOM
      RENAME_SET_VALUE Stratégie de planification vélo : > PLAN
    -> Sorter_4
Sorter_4
    SORT_PARM = NOM ALPHA ASCENDING
    SORTED -> AttributeValueMapper_2
AttributeValueMapper_2
    DEFAULT_VALUE = NON
    DIRECTION = Forward (Source To Destination)
    LUT = En cours,OUI,Non,NON,Oui,OUI
    SRC = PLAN
    VAL_ATTR = PLAN
    -> AttributeCreator_2
AttributeCreator_2
    ATTR_TABLE = SET_TO ENKTER = Oui
    -> TestFilter
TestFilter
    TEST_LIST = "BOOL_OP,OR,COMPOSITE_TEST,""""""<Unused>"""""",TEST_CLAUSE,TEST @Value(Statut) = I",INTERCO,"BOOL_OP,OR,COMPOSITE_TEST,""""""<Unused>"""""",TEST_CLAUSE,TEST @Value(Statut) = R",REG,"BOOL_OP,OR,COMPOSITE_TEST,""""""<Unused>"""""",TEST_CLAUSE,TEST @Value(Statut) = D",DEP,"BOOL_OP,OR,COMPOSITE_TEST,""""""<Unused>"""""",TEST_CLAUSE,TEST @Value(Statut) = C",AUTRE
    INTERCO -> FeatureJoiner_4 [RIGHT]
    REG -> FeatureJoiner [RIGHT]
    DEP -> FeatureJoiner_2 [RIGHT]
epci (reader ESRISHAPE_1)
    attributes: ID char(24), CODE_EPCI char(9), NOM_EPCI char(230), TYPE_EPCI char(150)
    -> FeatureJoiner_4 [LEFT]
FeatureJoiner_4
    ATTR_CONFLICT_RES = Use Left
    GEOMETRY_HANDLING = Use Left
    JOIN_KEYS = CODE_EPCI Code géographique : AUTO
    JOIN_MODE = Inner
    JOINED -> Reprojector_2
Reprojector_2
    DEST = EPSG:4326
    INTERPOLATION_TYPE_NAME = Nearest Neighbor
    RASTER_CELL_SIZE = Preserve Cells
    RASTER_TOLERANCE = 0.0
    SOURCE = Read from feature
    REPROJECTED -> Sorter_3
Sorter_3
    SORT_PARM = NOM_EPCI ALPHA ASCENDING
    SORTED -> EPCI_POLY (writer GEOJSON_3)
EPCI_POLY (writer GEOJSON_3)
    attributes: ID string, CODE_EPCI string, NOM_EPCI string, TYPE_EPCI string, ENKTER string, NOM string, Code géographique : int, A1_SQ002_. Code postal du siège : int, Nature juridique string, PLAN string, Statut string
COMMUNE (reader ESRISHAPE_4) [off]
    attributes: ID char(24), NOM_COM char(50), NOM_COM_M char(50), INSEE_COM char(5), STATUT char(24), POPULATION long, INSEE_ARR char(2), NOM_DEP char(30), INSEE_DEP char(3), NOM_REG char(35), INSEE_REG char(2), CODE_EPCI char(9)
    -> FeatureJoiner_3 [LEFT]
FeatureJoiner_3
    ATTR_CONFLICT_RES = Use Left
    GEOMETRY_HANDLING = Use Left
    JOIN_KEYS = INSEE_COM Code géographique : AUTO
    JOIN_MODE = Inner
    JOINED -> Reprojector_4
    JOINED -> FeatureJoiner_3_Joined
Reprojector_4
    DEST = EPSG:4326
    INTERPOLATION_TYPE_NAME = Nearest Neighbor
    RASTER_CELL_SIZE = Preserve Cells
    RASTER_TOLERANCE = 0.0
    SOURCE = Read from feature
    REPROJECTED -> AUTRE (writer GEOJSON_4)
AUTRE (writer GEOJSON_4)
    attributes: ID string, NOM_COM string, NOM_COM_M string, INSEE_COM string, STATUT string, POPULATION int, INSEE_ARR string, NOM_DEP string, INSEE_DEP string, NOM_REG string, INSEE_REG string, CODE_EPCI string
FeatureJoiner_3_Joined: Inspector [off]
departement (reader ESRISHAPE_3)
    attributes: ID char(24), NOM_DEP char(30), INSEE_DEP char(3), INSEE_REG char(2)
    -> FeatureJoiner_2 [LEFT]
FeatureJoiner_2
    ATTR_CONFLICT_RES = Use Left
    GEOMETRY_HANDLING = Use Left
    JOIN_KEYS = INSEE_DEP Code géographique : AUTO
    JOIN_MODE = Inner
    JOINED -> Reprojector_6
Reprojector_6
    DEST = EPSG:4326
    INTERPOLATION_TYPE_NAME = Nearest Neighbor
    RASTER_CELL_SIZE = Preserve Cells
    RASTER_TOLERANCE = 0.0
    SOURCE = Read from feature
    REPROJECTED -> AttributeKeeper_2
AttributeKeeper_2
    KEEP_ATTRS = Code géographique :,Statut,INSEE_REG,A1_SQ002_. Code postal du siège :,ENKTER,NOM,NOM_DEP,PLAN,Nature juridique,INSEE_DEP
    -> Sorter
Sorter
    SORT_PARM = NOM_DEP ALPHA ASCENDING
    SORTED -> DEPARTEMENT (writer GEOJSON_1)
DEPARTEMENT (writer GEOJSON_1)
    attributes: NOM_DEP string, INSEE_DEP string, INSEE_REG string, ENKTER string, NOM string, Code géographique : int, A1_SQ002_. Code postal du siège : int, Nature juridique string, PLAN string, Statut string
region (reader ESRISHAPE_2)
    attributes: ID char(24), NOM_REG char(35), INSEE_REG char(2), NOM_REG_2 char(80)
    -> FeatureJoiner [LEFT]
FeatureJoiner
    ATTR_CONFLICT_RES = Use Left
    GEOMETRY_HANDLING = Use Left
    JOIN_KEYS = INSEE_REG Code géographique : AUTO
    JOIN_MODE = Inner
    JOINED -> Reprojector_3
Reprojector_3
    DEST = EPSG:4326
    INTERPOLATION_TYPE_NAME = Nearest Neighbor
    RASTER_CELL_SIZE = Preserve Cells
    RASTER_TOLERANCE = 0.0
    SOURCE = Read from feature
    REPROJECTED -> Sorter_2
Sorter_2
    SORT_PARM = NOM_REG_2 ALPHA ASCENDING
    SORTED -> REGION (writer GEOJSON_2)
REGION (writer GEOJSON_2)
    attributes: ID string, NOM_REG string, INSEE_REG string, NOM_REG_2 string, ENKTER string, NOM string, Code géographique : int, A1_SQ002_. Code postal du siège : int, Nature juridique string, PLAN string, Statut string
